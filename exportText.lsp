(defun c:exportText ()
  (defun getValue (num entity)
 	 (progn (cdr (assoc num entity)))
  )
  	(setq ss (ssget "_A" (list (cons 0 "TEXT,MTEXT")))) 
	(setq i 0)
	(repeat (sslength ss)
		(setq ent (ssname ss i))
		(setq text (getValue 1 (entget ent)))
		(princ (strcat "\n" text "\n"))
		(setq i (1+ i))
	)
)
