(defun c:createPolesLayouts ()
	(setq layoutsPreviewSs (ssget "_A" (list (cons 0 "INSERT") (cons 8 "RZUT,RZUT_PLOTER"))))  
	(setq totalLayouts (sslength layoutsPreviewSs))
	(setq layoutsObj '())
	
	(defun getLayer (ent)
  		(progn (getValue 8 ent))
	)
	(defun getValue (num entity)
		(progn (cdr (assoc num entity)))
	)
	(defun getAttributeValue ( blk tag / val enx )
		(while
			(and
				(null val)
				(setq blk (entnext blk))
				(= "ATTRIB" (cdr (assoc 0 (setq enx (entget blk)))))
			)
			(if (= (strcase tag) (strcase (cdr (assoc 2 enx))))
				(setq val (cdr (assoc 1 (reverse enx))))
			)
		)
	)
	(defun selectLayoutType (lay)
		(if (equal lay "RZUT")
			(progn "A3")
			(progn "PLOTER")
        )
    )
	(defun copyPlot (layoutType cLayoutNumber allLayoutsNumber)
		(setq layoutName (strcat "ARK." cLayoutNumber " - " layoutType))
		(command "_layout" "_c" layoutType layoutName)
		(setvar "ctab" layoutName)
    )
	(defun rotateLayout (rotation)
		(command "_UCS" "_z" rotation)
		(command "_PLAN" "")
    )
	(defun setLayoutScale (entName)
		(command "_zoom" "_o" entName "")
		(command "_zoom" "_s" "2/1xp") ;1:1500
    )
	(defun changeTableNumbers (plotNumber allPlotNumber)
		(setq allLayoutObjects (ssget "X" (list (cons 410 (getvar "ctab")))))
		(setq number (strcat plotNumber "/" allPlotNumber))
		(setq j 0)
		(repeat (sslength allLayoutObjects)
			(setq layoutObject (ssname allLayoutObjects j))
			(setq layoutEntity (entget layoutObject))
			(setq layoutObjectType (getValue 0 layoutEntity))	
			(if (equal layoutObjectType "ACAD_TABLE")
				(if (not (equal "" (vla-gettext (vlax-ename->vla-object layoutObject) 8 2)))
					(vla-settext (vlax-ename->vla-object layoutObject) 8 2 number)
				)
			)
		(setq j (1+ j))
		)
	)
	(setq i 0)
	(repeat (sslength layoutsPreviewSs)
		(setq entName (ssname layoutsPreviewSs i)
				; (setq vla-blk (vlax-ename->vla-object entName))
				ent (entget entName)
				i (1+ i)
		)
	
	
		(setq numb (getAttributeValue entName "NUMBER"))
		(setq lay (getLayer ent))
		(setq plotType (selectLayoutType lay))
		(setq rotation (getValue 50 ent))
		(setq rotation (atoi (rtos (* 180.0 (/  rotation pi)) 2 0)	))
		(setq obj (list numb plotType rotation entName))
		(setq layoutsObj (cons obj layoutsObj))
	)
	
	(setq currentNumber 1)
	(repeat (length layoutsObj)
		(foreach obj layoutsObj
			(setq numb (nth 0 obj))
			(setq plotType (nth 1 obj))
			(setq rotation (nth 2 obj))
			(setq entName (nth 3 obj))
			
			(if (equal currentNumber (atoi numb))
				(progn
					(copyPlot plotType numb (itoa totalLayouts))
					(changeTableNumbers numb (itoa totalLayouts))
					(command "_mspace")
					(rotateLayout rotation)
					(setLayoutScale entName)
					(command "_pspace")
      
                )
            )
        )
		(setq currentNumber (1+ currentNumber))
    )
)
