(defun c:exportIntersectingLines ()
  (defun getValue (num entity)
	(progn (cdr (assoc num entity)))
  )
  (setq layerPoleEnt (entget (car (entsel "Wybierz warste ze slupami"))))
  (setq layerPoleEnt (getValue 8 layerPoleEnt))
  (setq s (ssget "_A" (list (cons 0 "INSERT") (cons 8 layerPoleEnt))))  
  (setq ADSS_M_LAY "ADSS_M")
  (setq ADSS_A_LAY "ADSS_A")
  (setq poleID_OK "NUMER_OK")
  (setq poleID "NUMER")
  (setq i 0)

  (defun fs ( ss / ssxunlocked ss i e sss)
    (defun ssxunlocked (/ filter elst ss)
      (setq filter "")
      (while (setq elst (tblnext "layer" (null elst)))
        (if (= 4 (logand 4 (cdr (assoc 70 elst))))
          (setq filter (strcat filter (cdr (assoc 2 elst)) ","))
        )
      )
      (and (= filter "")(setq filter "~*"))
      (setq ss (ssget "_X" (list (cons 0 "*") (cons -4 "<not") (cons 8 filter) (cons -4 "not>"))))
      ss
    )

    (defun fastsel (e / ss i ent)
      (vl-load-com)
      (setq ss (ssxunlocked))
      (setq i -1)
      (if (null sss) (setq sss (ssadd)))
      (while (setq ent (ssname ss (setq i (1+ i))))
        (if (not (eq e ent))
          (if (vlax-invoke (vlax-ename->vla-object e) 'intersectwith (vlax-ename->vla-object ent) acextendnone)
            (ssadd ent sss)
          )
        )
      )
      (ssadd e sss)
    )

    (setq i -1)
    (while (setq e (ssname ss (setq i (1+ i))))
    (fastsel e)
    )
    ;  (sssetfirst nil sss)
    (progn sss)
  )
  (defun getAllAttValues ( blk )
	(mapcar '(lambda ( att ) (cons (vla-get-tagstring att) (vla-get-textstring att))) (vlax-invoke blk 'getattributes))
  )
  (defun getPoleNumber_OK (blk)
	(setq attr (getAllAttValues blk))
	(setq attPoleNumber (getValue poleID_OK attr))
	(progn attPoleNumber)
  ) 
  (defun getPoleNumber (blk)
	(setq attr (getAllAttValues blk))
	(setq attPoleNumber (getValue poleID attr))
	(progn attPoleNumber)
  ) 
  (defun exportToExcel ()
	(setq columns '("A" "B" "C" "D"))
	(setq docsPath (strcat (getenv "USERPROFILE") "\\Documents"))
  	(setq emptyExcelPath (strcat docsPath "\\empty.xlsx"))
	(setq currentDwgPath (getvar "dwgprefix"))
	(setq finalExcelPath (strcat currentDwgPath "zestawienie_kabli.xlsx"))
    
	(OpenExcel emptyExcelPath "Arkusz1" nil)
	(setq rowCounter 1)
	(setq colCounter 0)
	(foreach dataList dataForExport
		(foreach data dataList
   			(setq cell (strcat (nth colCounter columns) (itoa rowCounter)))
			(PutCell cell (list data))
			(setq colCounter (1+ colCounter))
        )
		(setq rowCounter (1+ rowCounter))
		(setq colCounter 0)
	)
	(CloseExcel finalExcelPath)
	(princ "\nexported\n")
  )
  ;poleNumer, ADSS_M numb, ADSS_A numb
  (setq dataForExport '())
  (setq i 0)
  (repeat (sslength s)
    (setq ssobj (ssname s i))
    (setq poleEntity (entget ssobj))
    (setq vla-obj (vlax-ename->vla-object ssobj))
    (setq i (1+ i))

	(setq poleNumber_OK (getPoleNumber_OK vla-obj))
	(setq poleNumber (getPoleNumber vla-obj))
	(setq ADSS_M 0)
	(setq ADSS_A 0)
    
    
    (setq sel (ssadd))
    (setq sel (ssadd ssobj sel))
    (setq allFsObjects  (fs sel))
	
  	(setq j 0)
    (repeat (sslength allFsObjects)
      (setq fsSsobj (ssname allFsObjects j))
      (setq fsEnt (entget fsSsobj))
      (setq j (1+ j))
      (setq fsEntLayer (getValue 8 fsEnt))
      
      (if (= fsEntLayer ADSS_M_LAY)
        (setq ADSS_M (1+ ADSS_M))
      )
      (if (= fsEntLayer ADSS_A_LAY)
        (setq ADSS_A (1+ ADSS_A))
      )
    )
	(setq dataForExport (cons (list poleNumber_OK poleNumber ADSS_M ADSS_A)  dataForExport))
  );end of poles ss
  
  (exportToExcel)
  (princ)
)
