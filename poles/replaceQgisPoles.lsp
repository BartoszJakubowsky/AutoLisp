(defun c:replaceQgisPoles ()

(setq OLDSNAP (getvar "OSMODE"))
(setq OLDBLIP (getvar "BLIPMODE"))
(setq OLDCMDECHO (getvar "CMDECHO"))
(setq OLDLAYER (getvar "CLAYER"))
  
  
(defun switchDefaultSystemVars (onOff)
	(if (equal onOff T)
		(progn
			(setvar "OSMODE" 0)
			(setvar "CMDECHO" 0)
			(setvar "BLIPMODE" 0)
			(setvar "clayer" "0")
		)
		(progn
			(setvar "OSMODE" OLDSNAP)
			(setvar "CMDECHO" OLDCMDECHO)
			(setvar "BLIPMODE" OLDBLIP)
			(setvar "clayer" OLDLAYER)
		)
	)
)
(defun fs ( ss / ssxunlocked ss i e sss)
 (defun ssxunlocked (/ filter elst ss)
   (setq filter "")
   (while (setq elst (tblnext "layer" (null elst)))
     (if (= 4 (logand 4 (cdr (assoc 70 elst))))
       (setq filter (strcat filter (cdr (assoc 2 elst)) ","))
     )
   )
   (and (= filter "")(setq filter "~*"))
   (setq ss (ssget "_X" (list (cons 0 "*") (cons -4 "<not") (cons 8 filter) (cons -4 "not>"))))
   ss
 )

 (defun fastsel (e / ss i ent)
   (vl-load-com)
   (setq ss (ssxunlocked))
   (setq i -1)
   (if (null sss) (setq sss (ssadd)))
   (while (setq ent (ssname ss (setq i (1+ i))))
     (if (not (eq e ent))
       (if (vlax-invoke (vlax-ename->vla-object e) 'intersectwith (vlax-ename->vla-object ent) acextendnone)
         (ssadd ent sss)
       )
     )
   )
   (ssadd e sss)
 )

	(setq i -1)
	(while (setq e (ssname ss (setq i (1+ i))))
	(fastsel e)
	)
	;  (sssetfirst nil sss)
	(progn sss)
)
(defun getValue (num entity)
	(progn (cdr (assoc num entity)))
)
(defun editAtt( blk tag val )
	(setq tag (strcase tag))
	(vl-some
	'(lambda ( att )
			(if (= tag (strcase (vla-get-tagstring att)))
				(progn (vla-put-textstring att val) val)
			)
		)
		(vlax-invoke blk 'getattributes)
	)
)
(defun drawPole (vla-obj cords number)
	(setvar "clayer" "SLUP")
	(switchDefaultSystemVars T)
	(command "_insert" "SLUP" cords "1" "1" "0")
	(switchDefaultSystemVars nil)
  
	; (command "_scale" (entlast) "" cords 1000)
	(setq vla-blk (vlax-ename->vla-object (entlast)))

	(editAtt vla-blk "NUMER_OK" number)
)
(defun getNumberNextToInsert (ssobj)
	
	(defun getInsertCords (entity)
      (setq cords (getValue 10 entity))
      (progn cords)
    )
	;
		; (defun getSsAroundInsert (cords, diameter)
		; 	(command "_circle" cords diameter)
		; 	(setq circ (entlast))  
		; 	(setq sel (ssadd))
		; 	(setq sel (ssadd ssobj sel))
		; 	(setq surroundedObjects (fs sel))
		; 	(entdel circ)
		; 	(progn surroundedObjects)
		; )
		; (defun selectNumberFromSurroundedObjects (surroundedObjects)
		;   (setq j 0)
		;   (setq number "")
		;   (repeat (sslength surroundedObjects)
		;     (setq entity (entget (ssname surroundedObjects j)))
		;     (setq entLay (getValue 8 entity))
		;     (setq entType (getValue 0 entity))
		;     (setq j (1+ j))
		;     (if (and (or (equal entType "TEXT") (equal entType "MTEXT")) (equal entLay TARGETLAYER))
		;       (setq number (getValue 1 entity))
		;     )
			

		;   )
		;   (progn number)
		; )
		; (setq surroundedObjects (getSsAroundInsert insertCords 10))
		; (setq nearbyNumber (selectNumberFromSurroundedObjects surroundedObjects))
		; (progn nearbyNumber)
	;
	
	(setq insertCords (getInsertCords (entget ssobj)))
	(setq allText (ssget "_A" (list (cons 0 "TEXT,MTEXT") (cons 8 TARGETLAYER))))  
	
	(setq j 0)
  	(setq number "")
  	(setq lowestDistance 20.0)
	(repeat (sslength allText)
		(setq entity (entget (ssname allText j)))
		(setq textCords (getValue 10 entity))
		(setq textNumber (getValue 1 entity))
		(setq j (1+ j))
		
		(setq newDistance (distance insertCords textCords))
		(if (< newDistance lowestDistance)
			(progn 
				(setq lowestDistance newDistance)
				(setq number textNumber)
			)
		)
	)
	(progn number)
)


(setq layerEnt (entget (car (entsel "Wybierz warste z qgis"))))
(setq TARGETLAYER (getValue 8 layerEnt))
(setq s (ssget (list (cons 0 "INSERT") (cons 8 TARGETLAYER))))  

(setq i 0)
	(repeat (sslength s)
		(setq ssobj (ssname s i))
		(setq poleEntity (entget ssobj))
		(setq vla-obj (vlax-ename->vla-object ssobj))
		(setq i (1+ i))
		(setq number (getNumberNextToInsert ssobj))
		(setq poleCords (getValue 10 poleEntity))
   
   		(drawPole vla-obj poleCords number)

	)
  (princ)
)
