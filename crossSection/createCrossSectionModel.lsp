(defun c:createCrossSectionModel ()

  (setq globalX 0)
  (setq globalYHeight 9)
  (setq globalX_A 6.1)
  (setq globalX_B 26.7750)
  (setq globalCableX 16.4375)
  (setq globalNextX 32.8750)
  (setq warningAlertList '())
  (setq excelPolesPath (getfiled "Wybierz excel z zestawieniem słupów" "" "xlsx" 2))
  (setq crossSectionData (GetExcel excelPolesPath "Arkusz1" nil))
  
  (setq OLDLAYER (getvar "clayer"))

  (defun switchDefaultSystemVars (onOff)
	(if (equal onOff T)
		(progn
			(setvar "OSMODE" 0)
			(setvar "CMDECHO" 0)
			(setvar "BLIPMODE" 0)
			(setvar "clayer" "0")
		)
		(progn
			(setvar "OSMODE" OLDSNAP)
			(setvar "CMDECHO" OLDCMDECHO)
			(setvar "BLIPMODE" OLDBLIP)
			(setvar "clayer" OLDLAYER)
		)
	)
  )
  (defun editAtt( blk tag val )
		(setq tag (strcase tag))
		(vl-some
		'(lambda ( att )
				(if (= tag (strcase (vla-get-tagstring att)))
					(progn (vla-put-textstring att val) val)
				)
			)
			(vlax-invoke blk 'getattributes)
		)
  )
  (defun getPoleType (poleType)
    (if (or (vl-string-search "R" poleType) (vl-string-search "r" poleType))
		(progn "2")
		(progn "1")
    )
  )
  (defun getPoleHeight (poleType)
    (if (vl-string-search "9" poleType)
		(progn "9")
		(if (vl-string-search "10" poleType)
			(progn "10")
			(progn nil)
    	)
    )
   
  )
  (defun insertCrossSection (crossSectionNumber crossSectionHeight poleTypeA poleTypeB)
	(setq poleHeightA (getPoleHeight poleTypeA))
	(setq poleHeightB (getPoleHeight poleTypeB))
    (setq height nil)
    (if (or (= poleHeightA nil) (= poleHeightB nil))
		(progn 
			(setq warningAlertList (cons crossSectionNumber warningAlertList))
			(setq height "???")
        )
    )
    (if (not height)
      (progn 
        (if (>= (atof poleHeightA) (atof poleHeightB))
          (setq height poleHeightB)
          (setq height poleHeightA)
        )
        
        (if (= height "9")
          (setq height "6.0")
          (setq height "7.0")
        )
      )
    )
    
	(command "_insert" "CROSSSECTION" (list globalX 0) "1" "0" "0")
    (editAtt (vlax-ename->vla-object (entlast)) "NR" crossSectionNumber)
    (progn height)
  )
  (defun insertCables (cablesNumber cablesString height)

    (defun replaceUnderscore (str)
    	; (if (wcmatch str "_")
		; 	(progn (vl-string-subst "\n" "_" str))
		; 	(progn str)
        ; )
		(progn (vl-string-subst "\n" "_" str))
    )
    (setq cableInsert (strcat "CABLES_" cablesNumber))
    (command "_insert" cableInsert (list (+ globalX globalCableX) globalYHeight) "1" "0" "0")
      

      (setq cableString (replaceUnderscore cablesString))
      (editAtt (vlax-ename->vla-object (entlast)) "H" height)
      (editAtt (vlax-ename->vla-object (entlast)) "CABLES" cableString)
    )
  (defun insertPole (number typeP station x)
    (setq height (getPoleHeight typeP))
    (setq poleType (getPoleType typeP))
    (setq side nil)
    
    (if (= x globalX_A)
		(setq side "L")
		(setq side "R")
    )
    
    (if (= height nil)
      (setq height "8")
    )
    (if (= height "9")
      (setq height "7")
    )
    (if (= height "10")
      (setq height "8")
    )
    
    (setq insertPoleBlock (strcat "POLE_" poleType "_" height "_" side))
	(command "_insert" insertPoleBlock (list (+ globalX x) globalYHeight) "1" "0" "0" nil)
    
    ; (setq ent (entmakex (list '(0 . "INSERT")
    ;                           (cons 10 (list (+ globalX x) globalYHeight))
    ;                           '(2 . "POLE_2_7_L")
    ;                           '(41 . 1.0)
    ;                           '(42 . 1.0)
    ;                           '(43 . 1.0)
    ;                           '(50 . 0.0)
    ;                     )
    ;           )
    ; )
   
    (editAtt (vlax-ename->vla-object (entlast)) "NUMER" number)
    (editAtt (vlax-ename->vla-object (entlast)) "TYP_SLUPA" typeP)
    (editAtt (vlax-ename->vla-object (entlast)) "STACJA" station)
  )
  (defun createLayouts (entList)
	(setq totalLayouts (length entList))
	(defun getValue (num entity)
		(progn (cdr (assoc num entity)))
	)
	(defun copyPlot (layoutType cLayoutNumber allLayoutsNumber)
		(setq layoutName (strcat "ARK." cLayoutNumber " - " layoutType))
		(command "_layout" "_c" layoutType layoutName)
		(setvar "ctab" layoutName)
    )
	(defun zoomToObject (entName)
		(command "_zoom" "_o" entName "")
    )
	(defun changeTableNumbers (plotNumber allPlotNumber)
		(setq allLayoutObjects (ssget "X" (list (cons 410 (getvar "ctab")))))
		(setq number (strcat plotNumber "/" allPlotNumber))
		(setq j 0)
		(repeat (sslength allLayoutObjects)
			(setq layoutObject (ssname allLayoutObjects j))
			(setq layoutEntity (entget layoutObject))
			(setq layoutObjectType (getValue 0 layoutEntity))	
			(if (equal layoutObjectType "ACAD_TABLE")
				(if (not (equal "" (vla-gettext (vlax-ename->vla-object layoutObject) 8 2)))
					(vla-settext (vlax-ename->vla-object layoutObject) 8 2 number)
				)
			)
		(setq j (1+ j))
		)
	)
	(setq currentNumber 1)
	
    
	(foreach ent entList
		(setq entName (nth (- currentNumber 1)entList))
		(progn
			(copyPlot "A4" (itoa currentNumber) (itoa totalLayouts))
			(changeTableNumbers (itoa currentNumber) (itoa totalLayouts))
			(command "_mspace")
			(zoomToObject entName)
			(command "_pspace")
		)
		(setq currentNumber (1+ currentNumber))
	)
  )
  (defun warningAlert ()
    (setq warningNumbers "")
    (setq warningMessage "DO POPRAWY:\n")
    (if warningAlertList
      (progn
		(foreach str warningAlertList
			(if (= warningNumbers "")
				(setq warningNumbers str)
				(setq warningNumbers (strcat warningNumbers ", " str))
			)
        )
        (alert (strcat warningMessage warningNumbers))
      )
    )
  )
  (switchDefaultSystemVars T)
  (setvar "ctab" "Model")
  (setq createdCrossSections '())
  (foreach data crossSectionData
		(setq crossSectionNumber (nth 0 data))
		(setq crossSectionHeight (nth 1 data))
		(setq poleNumberA (nth 2 data))
		(setq poleTypeA (nth 3 data))
		(setq poleStationA (nth 4 data))
		(setq poleNumberB (nth 5 data))
		(setq poleTypeB (nth 6 data))
		(setq poleStationB (nth 7 data))
		(setq cablesNumber (nth 8 data))
		(setq cablesString (nth 9 data))
		; (setq cablesString "proj. ADSS 2J\nistn. AsXSn 4x95")

		
		(setq height (insertCrossSection crossSectionNumber crossSectionHeight poleTypeA poleTypeB))
		(setq createdCrossSections (append createdCrossSections (list (entlast))))
	
		
    	
		(insertCables cablesNumber cablesString height)
		(insertPole poleNumberA poleTypeA poleStationA globalX_A)
		(insertPole poleNumberB poleTypeB poleStationB globalX_B)
		(setq globalX (+ globalX globalNextX))
  )
  
  (createLayouts createdCrossSections)
  (switchDefaultSystemVars nil)
  (setvar "ctab" "Model")
  (command "_layer" "_off" "RAMKA" "")
  (warningAlert)
  (CloseExcel nil)
  ;do layoutu (setq entName (ssname layoutsPreviewSs i)
  (princ)
)
