(defun c:markPlots ()
(setq OLDSNAP (getvar "OSMODE"))
(setq OLDBLIP (getvar "BLIPMODE"))
(setq OLDCMDECHO (getvar "CMDECHO"))
(setq OLDLAYER (getvar "CLAYER"))
  
(setq excelPlotPath (getfiled "Wybierz excel z zestawieniem działek" "c:/Documents/" "xlsx" 2))	
(setq excelPlotList (GetExcel excelPlotPath "Arkusz1" nil))
  
(defun getValue (num entity)
	(progn (cdr (assoc num entity)))
)
(defun switchDefaultSystemVars (onOff)
	(if (equal onOff T)
		(progn
			(setvar "OSMODE" 0)
			(setvar "CMDECHO" 0)
			(setvar "BLIPMODE" 0)
		)
		(progn
			(setvar "OSMODE" OLDSNAP)
			(setvar "CMDECHO" OLDCMDECHO)
			(setvar "BLIPMODE" OLDBLIP)
		)
	)
)

(setq layerEnt (entget (car (entsel "Wybierz obiekt, na ktorym znajduja sie numery dzialek"))))
(setq lay (getValue 8 layerEnt))
(setq s (ssget "_A" (list (cons 0 "TEXT,MTEXT") (cons 8 lay))))  

(setq dimension 2.5)
(switchDefaultSystemVars T)
(foreach strPlot excelPlotList
	(setq plot (car strPlot))
	(setq i 0)
	(repeat (sslength s)
		(setq ssobj (ssname s i)
				entity (entget ssobj)
				plotName (getValue 1 entity)
				i (1+ i)
		)
  		(if (equal plotName plot)
			(progn
				(setq cords (getValue 11 entity))
				(setq cords1 (list (+ (nth 0 cords) dimension ) (+ (nth 1 cords) dimension)))
				(setq cords2 (list (- (nth 0 cords) dimension ) (- (nth 1 cords) dimension)))
				(command "_rectangle" cords1 cords2)
            )
        )
	)
	
)
(switchDefaultSystemVars nil)
(princ)
)
