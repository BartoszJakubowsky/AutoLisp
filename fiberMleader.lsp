(defun c:cc ()
  
  
  
(defun fs ( ss / ssxunlocked ss i e sss)
	(defun ssxunlocked (/ filter elst ss)
	(setq filter "")
	(while (setq elst (tblnext "layer" (null elst)))
		(if (= 4 (logand 4 (cdr (assoc 70 elst))))
		(setq filter (strcat filter (cdr (assoc 2 elst)) ","))
		)
	)
	(and (= filter "")(setq filter "~*"))
	(setq ss (ssget "_X" (list (cons 0 "*") (cons -4 "<not") (cons 8 filter) (cons -4 "not>"))))
	ss
	)

	(defun fastsel (e / ss i ent)
	(vl-load-com)
	(setq ss (ssxunlocked))
	(setq i -1)
	(if (null sss) (setq sss (ssadd)))
	(while (setq ent (ssname ss (setq i (1+ i))))
		(if (not (eq e ent))
		(if (vlax-invoke (vlax-ename->vla-object e) 'intersectwith (vlax-ename->vla-object ent) acextendnone)
			(ssadd ent sss)
		)
		)
	)
	(ssadd e sss)
	)

		(setq i -1)
		(while (setq e (ssname ss (setq i (1+ i))))
		(fastsel e)
		)
		;  (sssetfirst nil sss)
		(progn sss)
)
(defun getObjects (point)
  (command "_circle" point 10 5)
  (setq circle (entlast))
  (setq sel (ssadd))
  (setq sel (ssadd circle sel))
  (setq objects (fs sel))
  (entdel circle)
  (progn objects)
)
(setq descriptionPoint (getpoint "Wskaz punkt"))
(if (not descriptionPoint)
	(princ "Nie wskazano punktu")
	(progn
   		(setq fibers (getObjects descriptionPoint))
		(setq i 0)
		(repeat (sslength fibers)
			(setq ent (ssname fibers i)
					i (1+ i)
			)
		)
    )
)

)
