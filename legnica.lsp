(defun c:legica ()
  (setq newLayer "NAPOWIETRZNA")
  (setq OLDLAYER "0")
  (defun getValue (num entity)
		(progn (cdr (assoc num entity)))
  )
  
  (defun fs ( ss / ssxunlocked ss i e sss)
	(defun ssxunlocked (/ filter elst ss)
	(setq filter "")
	(while (setq elst (tblnext "layer" (null elst)))
		(if (= 4 (logand 4 (cdr (assoc 70 elst))))
		(setq filter (strcat filter (cdr (assoc 2 elst)) ","))
		)
	)
	(and (= filter "")(setq filter "~*"))
	(setq ss (ssget "_X" (list (cons 0 "*") (cons -4 "<not") (cons 8 filter) (cons -4 "not>"))))
	ss
	)

	(defun fastsel (e / ss i ent)
	(vl-load-com)
	(setq ss (ssxunlocked))
	(setq i -1)
	(if (null sss) (setq sss (ssadd)))
	(while (setq ent (ssname ss (setq i (1+ i))))
		(if (not (eq e ent))
		(if (vlax-invoke (vlax-ename->vla-object e) 'intersectwith (vlax-ename->vla-object ent) acextendnone)
			(ssadd ent sss)
		)
		)
	)
	(ssadd e sss)
	)

		(setq i -1)
		(while (setq e (ssname ss (setq i (1+ i))))
		(fastsel e)
		)
		;  (sssetfirst nil sss)
		(progn sss)
  )
  (defun switchDefaultSystemVars (onOff)
	(if (equal onOff T)
		(progn
			(setvar "OSMODE" 0)
			(setvar "CMDECHO" 0)
			(setvar "BLIPMODE" 0)
			(setvar "clayer" "0")
		)
		(progn
			(setvar "OSMODE" OLDSNAP)
			(setvar "CMDECHO" OLDCMDECHO)
			(setvar "BLIPMODE" OLDBLIP)
			(setvar "clayer" OLDLAYER)
		)
	)
  )
  (defun doesCrossPole(object)
	(setq isAerial nil)
	(setq j 0)
	(repeat (sslength object)
		(setq ssobjCheck (ssname object j))
		(setq entCheck (entget ssobjCheck))

		(setq entType (getValue 0 entCheck))
   
		(if (= entType "INSERT")
			(setq isAerial T)
        )
		(setq j (1+ j))
	)
    (progn isAerial)
  )
  (defun changeLayer(ent)
	(setq ent (subst (cons 8 newLayer) (assoc 8 ent) ent))
	(entmod ent)
  )
  (setq s (ssget (list (cons 0 "LWPOLYLINE"))))
  (switchDefaultSystemVars T)
  (setq i 0)
	(repeat (sslength s)
		(setq ssobj (ssname s i))
		; (setq line (entget ssobj))
		(setq sel (ssadd))
		(setq sel (ssadd ssobj sel))
   		(setq objects (fs sel))
		(setq isAerial (doesCrossPole objects))
		(if isAerial
			(changeLayer (entget ssobj))
        )

		(setq i (1+ i))
	)
  (switchDefaultSystemVars nil)
)
