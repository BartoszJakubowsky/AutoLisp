(defun c:jump ()
	(setq userLayout (getstring T "Gimme that layout... "))
	(if ( = (strlen userLayout)  0 )
		(progn 
			(alert "CAN'T FIND EMPTY LAYOUT!")
			(exit)
        )
    )
	(setq formattedUserLayout (vl-string-subst "_" "/" userLayout))
	(setq userLayoutSearch (strcase formattedUserLayout))
	(princ userLayoutSearch)
	; (setq userLayoutSearch (vl-string-trim "" userLayoutSearch))
	(setq targetLayout nil)
	(foreach layoutName (layoutlist)
		(setq layoutNameSearch (strcase layoutName))
		; (setq layoutNameSearch (vl-string-trim "" layoutNameSearch))
		
		(if (and (vl-string-search userLayoutSearch layoutNameSearch) (not targetLayout))
			(setq targetLayout layoutName)
        )
    )
	
	(if (not targetLayout)
		(progn 
			(setq alertMessage (strcat "CAN'T FIND " userLayout " OR ANYTHING SIMILAR :("))
			(alert alertMessage)
			(exit)
        )
    )
	(setvar "CTAB" targetLayout)
	(princ)
)
